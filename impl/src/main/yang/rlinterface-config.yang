module RLinterface-config {
    yang-version 1;
    namespace "urn:opendaylight:packet:RLinterface-config";
    prefix "BWcomput-config";

    description
        "This module contains the base configuration for
        implementation.";

    revision 2014-05-28 {
        description "Initial revision.";
    }

    container RLinterface-config {
    	list NodeConnectorCable{
            key "nodeConnector";
            leaf nodeConnector{
            description "srcnode";
            type string;
   			}
            leaf Cable{
            	type uint16;
            	default 5;
            }
    	}
    }
}
